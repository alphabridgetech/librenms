--
-- NMS-OPTICAL-EXT-CAP.my
-- MIB generated by MG-SOFT Visual MIB Builder Version 6.0  Build 88
-- Friday, May 11, 2024 at 10:14:56
--

	NMS-OPTICAL-EXT-CAP DEFINITIONS ::= BEGIN
        
		IMPORTS
			nms			
				FROM NMS
			Integer32, OBJECT-TYPE			
				FROM SNMPv2-SMI;
	
	
--                                                                                       
-- Node definitions
--
	
		-- xx.100
		extensions OBJECT IDENTIFIER ::= { nms 100 }
        
	
		-- xx.101
		notifications OBJECT IDENTIFIER ::= { nms 101 }
	
		
		-- xx.100.30
		ddm OBJECT IDENTIFIER ::= { extensions 30 }

		
		-- xx.100.30.2
		ddmTranscAlarmTable OBJECT-TYPE
			SYNTAX     SEQUENCE OF DdmTranscAlarmEntry
		    MAX-ACCESS not-accessible
		    STATUS     current
		    DESCRIPTION
		            "A list of  ddm transceiver alarm information."
		    ::= { ddm 2}

		
		-- xx.100.30.2.1
		ddmTranscAlarmEntry OBJECT-TYPE
			SYNTAX     DdmTranscAlarmEntry
		    MAX-ACCESS not-accessible
		    STATUS     current
		    DESCRIPTION
				"entry for ddm transceiver alarm information."
			INDEX      { ddmAlarmIfIndex }
			::= { ddmTranscAlarmTable 1 }

		
		DdmTranscAlarmEntry ::=
		SEQUENCE {
			ddmAlarmIfIndex
				INTEGER,
			ddmAlarmInfo
				OCTET STRING
		}

		
		-- xx.100.30.2.1.1
		ddmAlarmIfIndex OBJECT-TYPE
			SYNTAX INTEGER
			MAX-ACCESS read-only
			STATUS current
			DESCRIPTION
				"interface NO."
			::= { ddmTranscAlarmEntry 1 }

		
		-- xx.100.30.2.1.2
		ddmAlarmInfo OBJECT-TYPE
			SYNTAX OCTET STRING (SIZE(0..512))
			MAX-ACCESS read-only
			STATUS current
			DESCRIPTION
				"ddm transceiver alarm information."
			::= { ddmTranscAlarmEntry 2 }
	
		
		-- xx.101.110
		transceiverMonitor OBJECT IDENTIFIER ::= { notifications 110 }
		
		
		-- xx.101.110.1
		transceiverMonitorAlarmEvent NOTIFICATION-TYPE
			STATUS current
			DESCRIPTION "transceiver monitor alarm event."
			::= { transceiverMonitor 1 }

		
		-- xx.101.110.2
		transceiverMonitorWarnEvent NOTIFICATION-TYPE
			STATUS current
			DESCRIPTION "transceiver monitor warn event."
			::= { transceiverMonitor 2 }

		
	
	END

--
-- NMS-OPTICAL-EXT-CAP.my
--
