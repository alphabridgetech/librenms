--
-- NMS.my
-- MIB generated by MG-SOFT Visual MIB Builder Version 6.0  Build 88
-- Friday, May 14, 2021 at 10:09:33
--

	NMS DEFINITIONS ::= BEGIN
 
		IMPORTS
			enterprises, MODULE-IDENTITY, OBJECT-IDENTITY			
				FROM SNMPv2-SMI;
	
	
		-- xx.1.1
		nmsGlobalModule MODULE-IDENTITY 
			LAST-UPDATED "202105131943Z"		-- May 13, 2021 at 19:43 GMT
			ORGANIZATION 
				""
			CONTACT-INFO 
				""
			DESCRIPTION 
				"All enterprise's private MIB nodes for NMS."
			REVISION "202105140947Z"		-- May 14, 2021 at 09:47 GMT
			DESCRIPTION 
				"init"
			::= { nmsModule 1 }

		
	
--
-- Node definitions
--
	
		-- xx
		nms OBJECT-IDENTITY
			STATUS current
			DESCRIPTION 
				"The root of the OID sub-tree assigned to Company by the Internet Assigned Numbers Authority (IANA)"
			::= { enterprises 58158 }

		
		-- xx.1
		nmsModule OBJECT IDENTIFIER ::= { nms 1 }

		
		-- xx.2
		nmsGeneric OBJECT-IDENTITY
			STATUS current
			DESCRIPTION 
				"Sub-tree for common object and event definitions"
			::= { nms 2 }

		
		-- xx.3
		nmsProducts OBJECT-IDENTITY
			STATUS current
			DESCRIPTION 
				"Sub-tree for specific object and event definitions"
			::= { nms 3 }

		
		-- xx.4
		nmsCaps OBJECT-IDENTITY
			STATUS current
			DESCRIPTION 
				"Sub-tree for agent profiles"
			::= { nms 4 }

		
		-- xx.5
		nmsReqs OBJECT-IDENTITY
			STATUS current
			DESCRIPTION 
				"Sub-tree for management application requirements"
			::= { nms 5 }

		
		-- xx.6
		nmsExpr OBJECT-IDENTITY
			STATUS current
			DESCRIPTION 
				"Sub-tree for experimental definitions"
			::= { nms 6 }

		
	
	END

--
-- NMS.my
--
