--
-- NMS-CABLE-DIAG-MIB.my
-- MIB generated by MG-SOFT Visual MIB Builder Version 6.0  Build 88
-- Thursday, April 30, 2024 at 10:09:25
--

NMS-CABLE-DIAG-MIB DEFINITIONS ::= BEGIN
  IMPORTS
	TEXTUAL-CONVENTION			FROM SNMPv2-TC
	MODULE-IDENTITY,OBJECT-TYPE,
	Unsigned32,Integer32			FROM SNMPv2-SMI
	RowStatus,TruthValue			FROM SNMPv2-TC
	nmsModule				    FROM NMS;

	cableDiag OBJECT IDENTIFIER ::= { nmsModule 9 }

    cableDiagTable  OBJECT-TYPE
        SYNTAX  SEQUENCE OF cableDiagEntry
        MAX-ACCESS  not-accessible
        STATUS  current
        DESCRIPTION
            "A table that contains the cable situation for each port."
        ::= { cableDiag 1 }

    cableDiagEntry OBJECT-TYPE
        SYNTAX  cableDiagEntry
        MAX-ACCESS  not-accessible
        STATUS  current
        DESCRIPTION
            "A list of cable situations for each port on the device."
        INDEX   { cableDiagPortIndex }
        ::= { cableDiagTable 1 }

    cableDiagEntry ::= 
        SEQUENCE {
            cableDiagPortIndex
                INTEGER,
			cableDiagPortType
				INTEGER,
			cableDiagLinkStatus
				INTEGER,
			cableDiagPair1Status
				INTEGER,
			cableDiagPair2Status
				INTEGER,
			cableDiagPair3Status
				INTEGER,
			cableDiagPair4Status
				INTEGER,
			cableDiagPair1Length
				INTEGER,
			cableDiagPair2Length
				INTEGER,
			cableDiagPair3Length
				INTEGER,
			cableDiagPair4Length
				INTEGER,
			cableDiagAction
				INTEGER,
			cableDiagStatus
				INTEGER	                
        }

    cableDiagPortIndex OBJECT-TYPE
        SYNTAX  INTEGER (0..65535)
        MAX-ACCESS  read-only
        STATUS  current
        DESCRIPTION
        "This object indicates the module's port number.(1..Max port
        number in the module)"
    ::= { cableDiagEntry 1 }

    cableDiagPortType OBJECT-TYPE
    	SYNTAX INTEGER {
    			fastEthernet(0),
    			gigaEthernet(1),
    			other(2)
    	    	}
        MAX-ACCESS  read-only
        STATUS current
        DESCRIPTION
            "Indicates the supported port data rate classification."
    ::= { cableDiagEntry 2 }
    
      cableDiagLinkStatus OBJECT-TYPE
        SYNTAX INTEGER {
               link-down(0),
               link-up(1),
               other(2)
               }
        MAX-ACCESS  read-only
        STATUS  current
        DESCRIPTION
            "This object indicates the link status."
    ::= { cableDiagEntry 3 }
       
    cableDiagPair1Status OBJECT-TYPE
        SYNTAX  INTEGER {
               ok(0),
               open(1),
               short(2),
               open-short(3),
               crosstalk(4),
               unknown(5),
               count(6),
               no-cable(7),
               other(8)
               }
        MAX-ACCESS  read-only
        STATUS  current
        DESCRIPTION
            "This object indicates the status of pair 1 of the cable."
        ::= { cableDiagEntry 4 }
        
    cableDiagPair2Status OBJECT-TYPE
        SYNTAX  INTEGER {
               ok(0),
               open(1),
               short(2),
               open-short(3),
               crosstalk(4),
               unknown(5),
               count(6),
               no-cable(7),
               other(8)
               }
        MAX-ACCESS  read-only
        STATUS  current
        DESCRIPTION
            "This object indicates the status of pair 2 of the cable."
        ::= { cableDiagEntry 5 }        

    cableDiagPair3Status OBJECT-TYPE
        SYNTAX  INTEGER {
               ok(0),
               open(1),
               short(2),
               open-short(3),
               crosstalk(4),
               unknown(5),
               count(6),
               no-cable(7),
               other(8)
               }
        MAX-ACCESS  read-only
        STATUS  current
        DESCRIPTION
            "This object indicates the status of pair 3 of the cable."
        ::= { cableDiagEntry 6 }        

    cableDiagPair4Status OBJECT-TYPE
        SYNTAX  INTEGER {
               ok(0),
               open(1),
               short(2),
               open-short(3),
               crosstalk(4),
               unknown(5),
               count(6),
               no-cable(7),
               other(8)
               }
        MAX-ACCESS  read-only
        STATUS  current
        DESCRIPTION
            "This object indicates the status of pair 4 of the cable."
        ::= { cableDiagEntry 7 }
                           
    cableDiagPair1Length OBJECT-TYPE
        SYNTAX  INTEGER
        MAX-ACCESS  read-only
        STATUS  current
        DESCRIPTION
            "This object indicates the approx. length or length to the failure of 
            pair 1 of the cable. This value is in meter units."
        ::= { cableDiagEntry 8 } 
        
    cableDiagPair2Length OBJECT-TYPE
        SYNTAX  INTEGER
        MAX-ACCESS  read-only
        STATUS  current
        DESCRIPTION
            "This object indicates the approx. length or length to the failure of 
            pair 2 of the cable. This value is in meter units."
        ::= { cableDiagEntry 9 }  
        
    cableDiagPair3Length OBJECT-TYPE
        SYNTAX  INTEGER
        MAX-ACCESS  read-only
        STATUS  current
        DESCRIPTION
            "This object indicates the approx. length or length to the failure of 
            pair 3 of the cable. This value is in meter units."
        ::= { cableDiagEntry 10 }   
        
    cableDiagPair4Length OBJECT-TYPE
        SYNTAX  INTEGER
        MAX-ACCESS  read-only
        STATUS  current
        DESCRIPTION
            "This object indicates the approx. length or length to the failure of 
            pair 4 of the cable. This value is in meter units. "
        ::= { cableDiagEntry 11 }                         
        
	cableDiagAction OBJECT-TYPE 
        SYNTAX  INTEGER {
               action(1),
               processing(2),
               other(3)
               }
        MAX-ACCESS  read-write
        STATUS  current
        DESCRIPTION
            "Function to run the cable diagnostic on selected port."
        ::= { cableDiagEntry 12 } 
        
    cableDiagStatus OBJECT-TYPE 
        SYNTAX  INTEGER {
               not-run(1),
               processing(2),
               last-test-ok(3),
               last-test-failed(4)
               }
        MAX-ACCESS  read-only
        STATUS  current
        DESCRIPTION
            "Indicates the status of cable diagnostics on the port.
            	not-run - cable diagnostics has never been run for this port
            	processing - cable diagnostics is currently running on the port
            	last-test-ok - the last cable diagnostics done on the port was successful
            	last-test-failed - the last cable diagnostics done on the port failed"
        ::= { cableDiagEntry 13 } 
        
       
END
