--
-- NMS-PORT-MIB.my
-- MIB generated by MG-SOFT Visual MIB Builder Version 6.0  Build 88
-- Tuesday, November 21, 2023 at 17:30:30
--

	NMS-PORT-MIB DEFINITIONS ::= BEGIN
 
		IMPORTS
			nmsModule			
				FROM NMS			
			OBJECT-GROUP, NOTIFICATION-GROUP			
				FROM SNMPv2-CONF			
			Integer32, OBJECT-TYPE, MODULE-IDENTITY			
				FROM SNMPv2-SMI;
	
	
		-- xx.7.1
		pctrlModule MODULE-IDENTITY 
			LAST-UPDATED "202311211721Z"		-- November 21, 2023 at 17:21 GMT
			ORGANIZATION 
				""
			CONTACT-INFO 
				""
			DESCRIPTION 
				"Define port control private MIB nodes for NMS."
			::= { pctrl 1 }

		
	
--
-- Node definitions
--
	
		-- xx.7
		pctrl OBJECT IDENTIFIER ::= { nmsModule 7 }

		
		-- xx.7.2
		portControlTable OBJECT-TYPE
			SYNTAX SEQUENCE OF PortControlEntry
			MAX-ACCESS not-accessible
			STATUS current
			DESCRIPTION
				"Indicates the physical attributes of the Ethernet interface.
				 This table lists the physical attributes of various Ethernet interfaces."
			::= { pctrl 2 }

		
		-- xx.7.2.1
		portControlEntry OBJECT-TYPE
			SYNTAX PortControlEntry
			MAX-ACCESS not-accessible
			STATUS current
			DESCRIPTION
				"Indicates the physical attributes of the Ethernet interface.
				 This table lists the physical attributes of various Ethernet interfaces."
			INDEX { portControlIndex }
			::= { portControlTable 1 }

		
		PortControlEntry ::=
			SEQUENCE { 
				portControlIndex
					Integer32,
				portControlAdminStatus
					INTEGER,
				portControlOperStatus
					INTEGER,
				portControlAdminSpeed
					INTEGER,
				portControlAdminDuplex
					INTEGER,
				portControlOperSpeed
					INTEGER,
				portControlOperDuplex
					INTEGER,
				portControlNegotiation
					INTEGER,
				portControlFlowControl
					INTEGER,
				portControlMtu
					Integer32,
				portControlComboPrefer
					INTEGER,
				portControlComboType
					INTEGER,
				portControlPortMode
					INTEGER
			 }

		-- xx.7.2.1.1
		portControlIndex OBJECT-TYPE
			SYNTAX Integer32 (1..2147483647)
			MAX-ACCESS read-only
			STATUS deprecated
			DESCRIPTION
				"Interface index(es) of port(s) present on the device."
			::= { portControlEntry 1 }

		
		-- xx.7.2.1.2
		portControlAdminStatus OBJECT-TYPE
			SYNTAX INTEGER
				{
				up(1),
				down(2),
				testing(3)
				}
			MAX-ACCESS read-write
			STATUS current
			DESCRIPTION
				"The desired state of the interface."
			::= { portControlEntry 2 }

		
		-- xx.7.2.1.3
		portControlOperStatus OBJECT-TYPE
			SYNTAX INTEGER
				{
				up(1),
				down(2),
				testing(3),
				unknown(4),
				dormant(5),
				notPresent(6),
				lowerLayerDown(7)
				}
			MAX-ACCESS read-only
			STATUS current
			DESCRIPTION
				"The current operational state of the interface."
			::= { portControlEntry 3 }

		
		-- xx.7.2.1.4
		portControlAdminSpeed OBJECT-TYPE
			SYNTAX INTEGER
				{
				auto(0),
				speed10Mb(1),
				speed100Mb(2),
				speed1000Mb(3),
				unknown(4),
				speed2500Mb(5),
				speed10Gb(6),
				speed25Gb(7),
				speed40Gb(8),
				speed100Gb(9)
				}
			MAX-ACCESS read-write
			STATUS current
			DESCRIPTION
				"port speed settings.
				 This attribute apply physical port and aggreate port."
			::= { portControlEntry 4 }

		
		-- xx.7.2.1.5
		portControlAdminDuplex OBJECT-TYPE
			SYNTAX INTEGER
				{
				auto(0),
				full(1),
				half(2),
				unknown(3)
				}
			MAX-ACCESS read-write
			STATUS current
			DESCRIPTION
				"port duplex settings.
				 This attribute apply physical port and aggreate port."
			::= { portControlEntry 5 }

		
		-- xx.7.2.1.6
		portControlOperSpeed OBJECT-TYPE
			SYNTAX INTEGER
				{
				other(0),
				speed10Mb(1),
				speed100Mb(2),
				speed1000Mb(3),
				unknown(4),
				speed2500Mb(5),
				speed10Gb(6),
				speed25Gb(7),
				speed40Gb(8),
				speed100Gb(9)
				}
			MAX-ACCESS read-only
			STATUS current
			DESCRIPTION
				"After two port have negotiated the speed status,and this object
				 is the working speed status. while the port link status is down ,
				 then the speed status is unknown(4).
				 This attribute apply physical port and aggreate port."
			::= { portControlEntry 6 }

		
		-- xx.7.2.1.7
		portControlOperDuplex OBJECT-TYPE
			SYNTAX INTEGER
				{
				full(1),
				half(2),
				unknown(3)
				}
			MAX-ACCESS read-only
			STATUS current
			DESCRIPTION
				"After two port have negotiated the duplex status, and this object
				 is the working duplex status. while the port link status is down ,
				 then the speed status is unknown(3).
				 This attribute apply physical port and aggreate port"
			::= { portControlEntry 7 }

		
		-- xx.7.2.1.8
		portControlNegotiation OBJECT-TYPE
			SYNTAX INTEGER
				{
				enabled(1),
				disabled(2)
				}
			MAX-ACCESS read-write
			STATUS current
			DESCRIPTION
				"Indicates the auto-negotiation mode of the Ethernet interface. 
				 By default, auto-negotiation is enabled. The three objects, portControlAdminSpeed, 
				 portControlAdminDuplex, and portControlNegotiation are associated with each other.
				 When both portControlAdminSpeed and portControlAdminDuplex are auto-negotiation, 
				 the value of portControlNegotiation is enabled(1)."
			::= { portControlEntry 8 }		

		
		-- xx.7.2.1.9
		portControlFlowControl OBJECT-TYPE
			SYNTAX INTEGER
				{
				on(1),
				off(2),
				unknown(3)
				}
			MAX-ACCESS read-write
			STATUS current
			DESCRIPTION
				"Flow control of a port management status.
				 This attribute apply physical port and aggreate port"
			::= { portControlEntry 9 }		

		
		-- xx.7.2.1.10
		portControlMtu OBJECT-TYPE
			SYNTAX Integer32 (46..10222)
			MAX-ACCESS read-write
			STATUS current
			DESCRIPTION
				"Set the jumboframe max length of this port."
			::= { portControlEntry 10 }		

		
		-- xx.7.2.1.11
		portControlComboType OBJECT-TYPE
			SYNTAX INTEGER
				{
				copper(1),
				fiber(2),
				other(3),
				auto-copper(4),
				auto-fiber(5)
				}
			MAX-ACCESS read-write
			STATUS current
			DESCRIPTION
				"The port of combo mode settings."
			::= { portControlEntry 11 }

		
		-- xx.7.2.1.12
		portControlPortMode OBJECT-TYPE
			SYNTAX INTEGER
				{
				copper(1),
				fiber(2),
				other(3)
				}
			MAX-ACCESS read-only
			STATUS current
			DESCRIPTION
				"Indicates combo mode of this port."
			::= { portControlEntry 12 }

			
	END

--
-- NMS-PORT-MIB.my
--
