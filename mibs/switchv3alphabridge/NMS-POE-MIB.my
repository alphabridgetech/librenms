--
-- NMS-POE-MIB.my
-- MIB generated by MG-SOFT Visual MIB Builder Version 6.0  Build 88
-- Thursday, January 4, 2024 at 11:14:25
--

	NMS-POE-MIB DEFINITIONS ::= BEGIN
 
		IMPORTS
			nmsModule			
				FROM NMS			
			OBJECT-GROUP			
				FROM SNMPv2-CONF			
			Integer32, OBJECT-TYPE, MODULE-IDENTITY			
				FROM SNMPv2-SMI;
	
	
		-- xx.5.1
		poeModule MODULE-IDENTITY 
			LAST-UPDATED "202401041114Z"		-- January 4, 2024 at 11:14 GMT
			ORGANIZATION 
				""
			CONTACT-INFO 
				""
			DESCRIPTION 
				"Add pseStateReservedPower, pseStateTotalAvailablePower, portStateVoltage,
				portStateMaximumPower, portStateLegacy, portStatePowerSupplyMode."
			REVISION "202401041114Z"		-- January 4, 2024 at 11:14 GMT
			DESCRIPTION 
				"PoE module for NMS."
			REVISION "202105211854Z"		-- May 21, 2021 at 18:54 GMT
			DESCRIPTION 
				"init"                                      
			::= { poe 1 }

		
	
--
-- Node definitions
--
	
		-- xx.5
		poe OBJECT IDENTIFIER ::= { nmsModule 5 }

		
		-- xx.5.2
		poeTraps OBJECT IDENTIFIER ::= { poe 2 }

		
		-- xx.5.3
		pseStateTable OBJECT-TYPE
			SYNTAX SEQUENCE OF PseStateEntry
			MAX-ACCESS not-accessible
			STATUS current
			DESCRIPTION
				"Pse state table nodes."
			::= { poe 3 }

		
		-- xx.5.3.1
		pseStateEntry OBJECT-TYPE
			SYNTAX PseStateEntry
			MAX-ACCESS not-accessible
			STATUS current
			DESCRIPTION
				"Pse state table entry."
			INDEX { pseStateGroupIndex }
			::= { pseStateTable 1 }

		
		PseStateEntry ::=
			SEQUENCE { 
				pseStateGroupIndex
					Integer32,
				pseStatePowerConsume
					Integer32,
				pseStatePoweredPorts
					Integer32,
				pseStateReservedPower
					Integer32,
				pseStateTotalAvailablePower
					Integer32
			 }

		-- xx.5.3.1.1
		pseStateGroupIndex OBJECT-TYPE
			SYNTAX Integer32 (1..2147483647)
			MAX-ACCESS not-accessible
			STATUS current
			DESCRIPTION
				"Pse group index."
			::= { pseStateEntry 1 }

		
		-- xx.5.3.1.2
		pseStatePowerConsume OBJECT-TYPE
			SYNTAX Integer32
			MAX-ACCESS read-only
			STATUS current
			DESCRIPTION
				"Pse's power consumption, unit is 0.1 watt."
			::= { pseStateEntry 2 }

		
		-- xx.5.3.1.3
		pseStatePoweredPorts OBJECT-TYPE
			SYNTAX Integer32
			MAX-ACCESS read-only
			STATUS current
			DESCRIPTION
				"Pse powered ports."
			::= { pseStateEntry 3 }

		
		-- xx.5.3.1.4
		pseStateReservedPower OBJECT-TYPE
			SYNTAX Integer32 (0..50)
			MAX-ACCESS read-write
			STATUS current
			DESCRIPTION
				"Indicates the percentage of reserved power to total power."
			::= { pseStateEntry 4 }

		
		-- xx.5.3.1.5
		pseStateTotalAvailablePower OBJECT-TYPE
			SYNTAX Integer32
			MAX-ACCESS read-only
			STATUS current
			DESCRIPTION
				"The total available power of POE, unit is 0.1 watt."
			::= { pseStateEntry 5 }

		
		-- xx.5.4
		portStateTable OBJECT-TYPE
			SYNTAX SEQUENCE OF PortStateEntry
			MAX-ACCESS not-accessible
			STATUS current
			DESCRIPTION
				"Port state table nodes."
			::= { poe 4 }

		
		-- xx.5.4.1
		portStateEntry OBJECT-TYPE
			SYNTAX PortStateEntry
			MAX-ACCESS not-accessible
			STATUS current
			DESCRIPTION
				"Port state table entry."
			INDEX { portStateGroupIndex, portStateIndex }
			::= { portStateTable 1 }

		
		PortStateEntry ::=
			SEQUENCE { 
				portStateGroupIndex
					Integer32,
				portStateIndex
					Integer32,
				portStateDesc
					OCTET STRING,
				portStateIcut
					Integer32,
				portStatePower
					Integer32,
				portStateVoltage
					Integer32,
				portStateMaximumPower
					Integer32,
				portStateLegacy
					Integer32,
				portStatePowerSupplyMode
					Integer32
			 }

		-- xx.5.4.1.1
		portStateGroupIndex OBJECT-TYPE
			SYNTAX Integer32 (1..2147483647)
			MAX-ACCESS not-accessible
			STATUS current
			DESCRIPTION
				"Pse group index."
			::= { portStateEntry 1 }

		
		-- xx.5.4.1.2
		portStateIndex OBJECT-TYPE
			SYNTAX Integer32 (1..2147483647)
			MAX-ACCESS not-accessible
			STATUS current
			DESCRIPTION
				"Port index."
			::= { portStateEntry 2 }

		
		-- xx.5.4.1.3
		portStateDesc OBJECT-TYPE
			SYNTAX OCTET STRING
			MAX-ACCESS read-only
			STATUS current
			DESCRIPTION
				"Port description."
			::= { portStateEntry 3 }

		
		-- xx.5.4.1.4
		portStateIcut OBJECT-TYPE
			SYNTAX Integer32
			MAX-ACCESS read-only
			STATUS current
			DESCRIPTION
				"Port current icut, unit is 0.1 mA."
			::= { portStateEntry 4 }

		
		-- xx.5.4.1.5
		portStatePower OBJECT-TYPE
			SYNTAX Integer32
			MAX-ACCESS read-only
			STATUS current
			DESCRIPTION
				"Port current power, unit is 0.1 watt."
			::= { portStateEntry 5 }

		
		-- xx.5.4.1.6
		portStateVoltage OBJECT-TYPE
			SYNTAX Integer32
			MAX-ACCESS read-only
			STATUS current
			DESCRIPTION
				"Port current voltage, unit is 0.1 V."
			::= { portStateEntry 6 }

		
		-- xx.5.4.1.7
		portStateMaximumPower OBJECT-TYPE
			SYNTAX Integer32 (0..90)
			MAX-ACCESS read-write
			STATUS current
			DESCRIPTION
				"Port maximum power, unit is watt.
				 0 indicates that the maximum power of the port is reset.
				 The maximum power ranges from 1 to 30 for an AT port 
				 and from 1 to 90 for a BT port"
			::= { portStateEntry 7 }

		
		-- xx.5.4.1.8
		portStateLegacy OBJECT-TYPE
			SYNTAX INTEGER
				{
				enabled(1),
				disabled(2)
				}
			MAX-ACCESS read-write
			STATUS current
			DESCRIPTION
				"This object indicates the compatibility detection of a non-standard device."
			::= { portStateEntry 8 }

		
		-- xx.5.4.1.9
		portStatePowerSupplyMode OBJECT-TYPE
			SYNTAX INTEGER
				{
				AT(1),
				BT(2),
				unknown(3)
				}
			MAX-ACCESS read-only
			STATUS current
			DESCRIPTION
				"Port power supply mode."
			::= { portStateEntry 9 }

		
		-- xx.5.10
		poeGroups OBJECT IDENTIFIER ::= { poe 10 }

		
		-- xx.5.10.1
		poeTableGroup OBJECT-GROUP
			OBJECTS { pseStatePowerConsume, pseStatePoweredPorts, portStateDesc, portStateIcut, portStatePower, 
					portStateVoltage, portStateMaximumPower, portStateLegacy, portStatePowerSupplyMode
				 }
			STATUS current
			DESCRIPTION 
				"Poe table nodes group."
			::= { poeGroups 1 }

		
	
	END

--
-- NMS-POE-MIB.my
--
