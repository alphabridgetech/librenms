--
-- NMS-LDET-MIB.my
-- MIB generated by MG-SOFT Visual MIB Builder Version 6.0  Build 88
-- Wednesday, May 9, 2024 at 15:21:17
--

	NMS-LDET-MIB DEFINITIONS ::= BEGIN
 
		IMPORTS
			nmsModule			
				FROM NMS			
			OBJECT-GROUP, NOTIFICATION-GROUP			
				FROM SNMPv2-CONF			
			Integer32, Gauge32, OBJECT-TYPE, MODULE-IDENTITY, NOTIFICATION-TYPE			
				FROM SNMPv2-SMI;
	
	
		-- xx.6.1
		ldetGlobalModule MODULE-IDENTITY 
			LAST-UPDATED "202405091521Z"		-- May 9, 2024 at 15:21 GMT
			ORGANIZATION 
				""
			CONTACT-INFO 
				""
			DESCRIPTION 
				"Define loop detection nodes."
			REVISION "202405091521Z"		-- May 9, 2024 at 15:21 GMT
			DESCRIPTION 
				"Added ldetGlobalModule and ldetPortTable nodes."
			REVISION "202302221035Z"		-- February 22, 2023 at 10:35 GMT
			DESCRIPTION 
				"init"
			::= { ldet 1 }

		
	
--
-- Node definitions
--
		
		-- xx.6
		ldet OBJECT IDENTIFIER ::= { nmsModule 6 }
		
		-- xx.6.1.1
		ldetGlobalEnabled OBJECT-TYPE
			SYNTAX INTEGER
				{
				enabled(1),
				disabled(2)
				}
			MAX-ACCESS read-write
			STATUS current
			DESCRIPTION
				"Global LDT enabled state."
			::= { ldetGlobalModule 1 }

		
		-- xx.6.1.2
		ldetGlobalInterval OBJECT-TYPE
			SYNTAX Integer32 (5..300)
			MAX-ACCESS read-write
			STATUS current
			DESCRIPTION
				"The interval between sending loop detection packets."
			::= { ldetGlobalModule 2 }

		
		-- xx.6.2
		ldetTraps OBJECT IDENTIFIER ::= { ldet 2 }

		
		-- xx.6.2.1
		loopDetect NOTIFICATION-TYPE
			OBJECTS { ldetPortifIndex }
			STATUS current
			DESCRIPTION 
				"Notify loop detect event."
			::= { ldetTraps 1 }

		
		-- xx.6.2.2
		loopRecover NOTIFICATION-TYPE
			OBJECTS { ldetPortifIndex }
			STATUS current
			DESCRIPTION 
				"Notify loop recover event."
			::= { ldetTraps 2 }

		
		-- xx.6.4
		ldetPortTable OBJECT-TYPE
			SYNTAX SEQUENCE OF LdetPortEntry
			MAX-ACCESS not-accessible
			STATUS current
			DESCRIPTION
				"Loop detection port state table."
			::= { ldet 4 }

		
		-- xx.6.4.1
		ldetPortEntry OBJECT-TYPE
			SYNTAX LdetPortEntry
			MAX-ACCESS not-accessible
			STATUS current
			DESCRIPTION
				"Loop detection port state entry."
			INDEX { ldetPortifIndex }
			::= { ldetPortTable 1 }

		
		LdetPortEntry ::=
			SEQUENCE { 
				ldetPortifIndex
					Integer32,
				ldetPortEnabled
					INTEGER,
				ldetPortRecoveryTime
					Integer32,
				ldetPortAction
					INTEGER,
				ldetPortStatus
					INTEGER 
			 }

		-- xx.6.4.1.1
		ldetPortifIndex OBJECT-TYPE
			SYNTAX Integer32 (1..2147483647)
			MAX-ACCESS not-accessible
			STATUS current
			DESCRIPTION
				"Port index."
			::= { ldetPortEntry 1 }

		
		-- xx.6.4.1.2
		ldetPortEnabled OBJECT-TYPE
			SYNTAX INTEGER
				{
				enabled(1),
				disabled(2)
				}
			MAX-ACCESS read-write
			STATUS current
			DESCRIPTION
				"Port LDT enabled status."
			::= { ldetPortEntry 2 }

		
		-- xx.6.4.1.3
		ldetPortAction OBJECT-TYPE
			SYNTAX INTEGER
				{
				alarm(1),
				down(2)
				}
			MAX-ACCESS read-write
			STATUS current
			DESCRIPTION
				"Port processing mode."
			::= { ldetPortEntry 3 }

		
		-- xx.6.4.1.4
		ldetPortStatus OBJECT-TYPE
			SYNTAX INTEGER
				{
				normal(0),
				alarm(1),
				down(2)
				}
			MAX-ACCESS read-only
			STATUS current
			DESCRIPTION
				"Port state."
			::= { ldetPortEntry 4 }		

		
		-- xx.6.9
		ldetGroups OBJECT IDENTIFIER ::= { ldet 9 }

		
		-- xx.6.9.1
		ldetTableGroup OBJECT-GROUP
			OBJECTS { ldetPortifIndex, ldetPortEnabled, ldetPortRecoveryTime, ldetPortAction, ldetPortStatus }
			STATUS current
			DESCRIPTION 
				"Loop detection table&scalar nodes."
			::= { ldetGroups 1 }

		
		-- xx.6.9.2
		ldetTrapGroup NOTIFICATION-GROUP
			NOTIFICATIONS { loopDetect, loopRecover }
			STATUS current
			DESCRIPTION 
				"Loop detection trap nodes."
			::= { ldetGroups 2 }

		
	
	END

--
-- NMS-LDET-MIB.my
--
